-- Module Example6-ASN1-Module (X.692:11/2008)
Example6-ASN1-Module {joint-iso-itu-t(2) asn1(1) ecn(4) examples(5)
  asn1-module6(18)} DEFINITIONS AUTOMATIC TAGS ::=
BEGIN

My-Special-1 ::= INTEGER(-1..10)

my-Special-1 My-Special-1 ::= 0

My-Special-2 ::= INTEGER(-10..10)

my-Special-2 My-Special-2 ::= 1

My-Special-3 ::= INTEGER(0..1000)

my-Special-3 My-Special-3 ::= 1000

END

-- Generated by Asnp, the ASN.1 pretty-printer of France Telecom R&D
